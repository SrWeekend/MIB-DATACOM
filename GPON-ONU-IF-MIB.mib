-- Generated by
-- confdc ++emit-mib GPON-ONU-IF-MIB.mib ++oid 1.3.6.1.4.1.3709.3.6.2 ++join-names force-capitalize ++top gponOnuIfMIB ++module GPON-ONU-IF-MIB -f /opt/dmos/output_pd2902/host//opt/confd/etc/confd/ietf-inet-types.fxs /opt/dmos/output_pd2902/host//opt/confd/etc/confd/ietf-yang-types.fxs /opt/dmos/output_pd2902/host/powerpc-buildroot-linux-gnu/sysroot/etc/confd/IANAifType-MIB.fxs /opt/dmos/output_pd2902/host/powerpc-buildroot-linux-gnu/sysroot/etc/confd/dmos-base.fxs /opt/dmos/output_pd2902/host/powerpc-buildroot-linux-gnu/sysroot/etc/confd/dmos-interfaces.fxs /opt/dmos/output_pd2902/host/powerpc-buildroot-linux-gnu/sysroot/etc/confd/dmos-types.fxs ++ /opt/dmos/output_pd2902/build/dmos-gpond-c592c91225a20334fc184e87933a8386cfddf35d/dmos-gpon-onu-mib.fxs
-- 2020-02-14 18:14:14
-- Namespace: urn:dmos-gpon-onu-mib

GPON-ONU-IF-MIB DEFINITIONS ::= BEGIN
IMPORTS
    MODULE-IDENTITY, OBJECT-TYPE,
    Integer32, Unsigned32, Counter32, Counter64,
    Gauge32, IpAddress, TimeTicks
        FROM SNMPv2-SMI
    TEXTUAL-CONVENTION, RowStatus, DateAndTime,
    TruthValue
        FROM SNMPv2-TC
;

gponOnuIfMIB MODULE-IDENTITY
    LAST-UPDATED "201808130000Z"
    ORGANIZATION "@ORGANIZATION"
    CONTACT-INFO "@CONTACT-INFO"
    DESCRIPTION "This module contains GPON ONU and UNI interfaces operational data for SNMP"
    REVISION "201808130000Z"
    DESCRIPTION "@REVISION-DESCRIPTION"
    ::= { 1 3 6 1 4 1 3709 3 6 2 }

String ::= TEXTUAL-CONVENTION
    DISPLAY-HINT "1t"
    STATUS      current
    DESCRIPTION "xs:string"
    SYNTAX      OCTET STRING

-- tagpath /status/interface/ifTable/ifEntry
onuIfTable OBJECT-TYPE
    SYNTAX      SEQUENCE OF OnuIfEntry
    MAX-ACCESS  not-accessible
    STATUS      current
    DESCRIPTION "This table represents ONU associated entities (e.g. ONU, Ethernet UNI)"
    ::= { gponOnuIfMIB 1 }

-- tagpath /status/interface/ifTable/ifEntry
onuIfEntry OBJECT-TYPE
    SYNTAX      OnuIfEntry
    MAX-ACCESS  not-accessible
    STATUS      current
    DESCRIPTION ""
    INDEX { onuifIndex }
        ::= { onuIfTable 1 }

OnuIfEntry ::=
    SEQUENCE {
        onuIfStatisticsInOctets Counter64,
        onuIfStatisticsInUcastPkts Counter64,
        onuIfStatisticsInMulticastPkts Counter64,
        onuIfStatisticsInBroadcastPkts Counter64,
        onuIfStatisticsInDiscards Counter64,
        onuIfStatisticsInErrors Counter64,
        onuIfStatisticsInUnknownProtos Counter64,
        onuIfStatisticsOutOctets Counter64,
        onuIfStatisticsOutUcastPkts Counter64,
        onuIfStatisticsOutMulticastPkts Counter64,
        onuIfStatisticsOutBroadcastPkts Counter64,
        onuIfStatisticsOutDiscards Counter64,
        onuIfStatisticsOutErrors Counter64,
        onuIfStatisticsInBwUsage Counter64,
        onuIfStatisticsOutBwUsage Counter64,
        onuifIndex Integer32,
        onuifDescr String,
        onuifType INTEGER,
        onuifName String,
        onuifAdminStatus INTEGER,
        onuifOperStatus INTEGER,
        onuIfOnuPowerTx String,
        onuIfOnuPowerRx String,
        onuIfAlias String,
        onuSysUpTime TimeTicks
    }

-- tagpath /status/interface/ifTable/ifEntry/statistics/ifInOctets
onuIfStatisticsInOctets OBJECT-TYPE
    SYNTAX      Counter64
    MAX-ACCESS  read-only
    STATUS      current
    DESCRIPTION "Ethernet UNI input octets"
    ::= { onuIfEntry 8 }

-- tagpath /status/interface/ifTable/ifEntry/statistics/ifInUcastPkts
onuIfStatisticsInUcastPkts OBJECT-TYPE
    SYNTAX      Counter64
    MAX-ACCESS  read-only
    STATUS      current
    DESCRIPTION "Ethernet UNI input unicast packets"
    ::= { onuIfEntry 9 }

-- tagpath /status/interface/ifTable/ifEntry/statistics/ifInMulticastPkts
onuIfStatisticsInMulticastPkts OBJECT-TYPE
    SYNTAX      Counter64
    MAX-ACCESS  read-only
    STATUS      current
    DESCRIPTION "Ethernet UNI input multicast packets"
    ::= { onuIfEntry 10 }

-- tagpath /status/interface/ifTable/ifEntry/statistics/ifInBroadcastPkts
onuIfStatisticsInBroadcastPkts OBJECT-TYPE
    SYNTAX      Counter64
    MAX-ACCESS  read-only
    STATUS      current
    DESCRIPTION "Ethernet UNI input broadcast packets"
    ::= { onuIfEntry 11 }

-- tagpath /status/interface/ifTable/ifEntry/statistics/ifInDiscards
onuIfStatisticsInDiscards OBJECT-TYPE
    SYNTAX      Counter64
    MAX-ACCESS  read-only
    STATUS      current
    DESCRIPTION "Ethernet UNI input discarded packets"
    ::= { onuIfEntry 12 }

-- tagpath /status/interface/ifTable/ifEntry/statistics/ifInErrors
onuIfStatisticsInErrors OBJECT-TYPE
    SYNTAX      Counter64
    MAX-ACCESS  read-only
    STATUS      current
    DESCRIPTION "Ethernet UNI input packets with errors"
    ::= { onuIfEntry 13 }

-- tagpath /status/interface/ifTable/ifEntry/statistics/ifInUnknownProtos
onuIfStatisticsInUnknownProtos OBJECT-TYPE
    SYNTAX      Counter64
    MAX-ACCESS  read-only
    STATUS      current
    DESCRIPTION "Ethernet UNI input packets with unknown protocol"
    ::= { onuIfEntry 14 }

-- tagpath /status/interface/ifTable/ifEntry/statistics/ifOutOctets
onuIfStatisticsOutOctets OBJECT-TYPE
    SYNTAX      Counter64
    MAX-ACCESS  read-only
    STATUS      current
    DESCRIPTION "Ethernet UNI output octets"
    ::= { onuIfEntry 15 }

-- tagpath /status/interface/ifTable/ifEntry/statistics/ifOutUcastPkts
onuIfStatisticsOutUcastPkts OBJECT-TYPE
    SYNTAX      Counter64
